module goldstone-ip {

    yang-version "1";

    namespace
      "http://goldstone.net/yang/goldstone-ip";

    prefix gs-ip;

    import goldstone-interfaces {
      prefix gs-if;
    }
    import goldstone-mgmt-interfaces {
      prefix gs-mgmt-if;
    }
    import goldstone-portchannel {
      prefix gs-pc;
    }
    import ietf-inet-types {
      prefix inet;
    }
    import ietf-yang-types {
      prefix yang;
    }

    organization
      "Goldstone";


    description
      "This module contains a collection of YANG definitions for
    configuring IP implementations.";

    revision "2020-10-13" {
      description "Initial revision.";
      reference
        "0.1.0";

    }


    feature ipv4-non-contiguous-netmasks {
      description
        "Indicates support for configuring non-contiguous
      subnet masks.";
    }

    typedef ip-address-origin {
      type enumeration {
        enum "other" {
          value 0;
          description
            "None of the following.";
        }
        enum "static" {
          value 1;
          description
            "Indicates that the address has been statically
          configured - for example, using NETCONF or a Command Line
          Interface.";
        }
        enum "dhcp" {
          value 2;
          description
            "Indicates an address that has been assigned to this
          system by a DHCP server.";
        }
        enum "link-layer" {
          value 3;
          description
            "Indicates an address created by IPv6 stateless
          autoconfiguration that embeds a link-layer address in its
          interface identifier.";
        }
        enum "random" {
          value 4;
          description
            "Indicates an address chosen by the system at

          random, e.g., an IPv4 address within 169.254/16, an
          RFC 4941 temporary address, or an RFC 7217 semantically
          opaque address.";
          reference
            "RFC 4941: Privacy Extensions for Stateless Address
                  Autoconfiguration in IPv6
             RFC 7217: A Method for Generating Semantically Opaque
                  Interface Identifiers with IPv6 Stateless
                  Address Autoconfiguration (SLAAC)";

        }
      }
      description
        "The origin of an address.";
    }

    typedef neighbor-origin {
      type enumeration {
        enum "other" {
          value 0;
          description
            "None of the following.";
        }
        enum "static" {
          value 1;
          description
            "Indicates that the mapping has been statically
          configured - for example, using NETCONF or a Command Line
          Interface.";
        }
        enum "dynamic" {
          value 2;
          description
            "Indicates that the mapping has been dynamically resolved
          using, e.g., IPv4 ARP or the IPv6 Neighbor Discovery
          protocol.";
        }
      }
      description
        "The origin of a neighbor entry.";
    }

    grouping ipv4-address-state {
      description
        "State variables for IPv4 addresses on the interface";

      leaf origin {
        type ip-address-origin;
        description
         "The origin of this address, e.g., statically configured,
         assigned by DHCP, etc..";
      }
    }

    grouping goldstone-ip { 
      description
        "Parameters for configuring IP on interfaces.

      If an interface is not capable of running IP, the server
      must not allow the client to configure these parameters.";
      container ipv4 {
        presence
          "Enables IPv4 unless the 'enabled' leaf
        (which defaults to 'true') is set to 'false'";
        description
          "Parameters for the IPv4 address family.";
        leaf enabled {
          type boolean;
          default 'true';
          description
            "Controls whether IPv4 is enabled or disabled on this
          interface.  When IPv4 is enabled, this interface is
          connected to an IPv4 stack, and the interface can send
          and receive IPv4 packets.";
        }

        leaf forwarding {
          type boolean;
          default 'false';
          description
            "Controls IPv4 packet forwarding of datagrams received by,
          but not addressed to, this interface.  IPv4 routers
          forward datagrams.  IPv4 hosts do not (except those
          source-routed via the host).";
        }

        leaf mtu {
          type uint16 {
            range "1312..9216" {
              error-message "Invalid MTU value";
              error-app-tag mtu-invalid;
            }

          }
          units "octets";
          default 9100;
          description
            "The size, in octets, of the largest IPv4 packet that the
          interface will send and receive.

          The server may restrict the allowed values for this leaf,
          depending on the interface's type.

          If this leaf is not configured, the operationally used MTU
          depends on the interface's type.";
          reference
            "RFC 791: Internet Protocol";

        }

        list address {
          key "ip";
          description
            "The list of configured IPv4 addresses on the interface.";
          leaf ip {
            type inet:ipv4-address-no-zone;
            description
              "The IPv4 address on the interface.";
          }

          choice subnet {
            mandatory true;
            description
              "The subnet can be specified as a prefix-length, or,
            if the server supports non-contiguous netmasks, as
            a netmask.";
            leaf prefix-length {
              type uint8 {
                range "0..32";
              }
              description
                "The length of the subnet prefix.";
            }
            leaf netmask {
              if-feature ipv4-non-contiguous-netmasks;
              type yang:dotted-quad;
              description
                "The subnet specified as a netmask.";
            }
          }  // choice subnet

          container state {
            config false;
            description "Operational state data for each IPv4 address
            configured on the interface";

            uses ipv4-address-state;
          }
        }  // list address

        list neighbor {
          key "ip";
          description
            "A list of mappings from IPv4 addresses to
          link-layer addresses.

          Entries in this list are used as static entries in the
          ARP Cache.";
          reference
            "RFC 826: An Ethernet Address Resolution Protocol";

          leaf ip {
            type inet:ipv4-address-no-zone;
            description
              "The IPv4 address of the neighbor node.";
          }

          leaf link-layer-address {
            type yang:phys-address;
            mandatory true;
            description
              "The link-layer address of the neighbor node.";
          }
        }  // list neighbor
      }  // container ipv4
    }

    augment /gs-if:interfaces/gs-if:interface {
      uses goldstone-ip;
    }

    augment /gs-mgmt-if:interfaces/gs-mgmt-if:interface {
      uses goldstone-ip;
    }

    augment /gs-pc:portchannel/gs-pc:portchannel-group/gs-pc:config {
      uses goldstone-ip;
    }



  }  // module goldstone-ip
