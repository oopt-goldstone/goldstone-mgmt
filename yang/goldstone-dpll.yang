module goldstone-dpll {
  yang-version "1";

  namespace "http://goldstone.net/yang/goldstone-dpll";
  prefix gs-dpll;

  organization
    "Goldstone";

  description
    "This module contains a collection of YANG definitions for
     managing DPLLs.";

  revision 2022-04-19 {
    description
      "Initial version.";
    reference
      "0.1.0";
  }

  typedef input-reference-ref {
    type leafref {
      path "/gs-dpll:dplls/gs-dpll:dpll/gs-dpll:input-references/gs-dpll:input-reference/gs-dpll:name";
    }
  }

  grouping dpll-config {
    leaf name {
      type string;
    }
    leaf mode {
      type enumeration {
        enum unknown;
        enum freerun;
        enum forced-holdover;
        enum forced-reference-lock;
        enum automatic;
        enum nco;
      }
    }
    leaf phase-slope-limit {
      type union {
        type enumeration {
          enum unlimitted;
        }
        type uint16; // unit ns/s
      }
    }
    leaf loop-bandwidth {
      type decimal64 {
        fraction-digits 16;
      }
    }
  }

  grouping dpll-state {
    leaf state {
      type enumeration {
        enum freerun;
        enum holdover;
        enum fast-lock;
        enum acquiring;
        enum lock;
      }
    }
    leaf selected-reference {
      type input-reference-ref;
    }
  }

  grouping input-references-config {
    leaf name {
      type string;
    }
    leaf priority {
      type uint8;
    }
  }

  grouping input-references-state {
    leaf-list alarm {
      type enumeration {
        enum los;
        enum scm;
        enum cfm;
        enum gst;
        enum pfm;
        enum sfm;
        enum eppsm;
        enum split-xom;
      }
    }
  }

  grouping input-reference-top {
    container input-references {
      list input-reference {
        key "name";
        leaf name {
          type leafref {
            path "../config/name";
          }
        }
        container config {
          uses input-references-config;
        }
        container state {
          config false;
          uses input-references-config;
          uses input-references-state;
        }
      }
    }
  }

  grouping dpll-top {
    container dplls {
      list dpll {
        key "name";
        leaf name {
          type leafref {
            path "../config/name";
          }
        }
        container config {
          uses dpll-config;
        }
        container state {
          config false;
          uses dpll-config;
          uses dpll-state;
        }

        uses input-reference-top;
      }
    }
  }

  uses dpll-top;
}
