module goldstone-gearbox {

  yang-version "1";

  namespace "http://goldstone.net/yang/goldstone-gearbox";
  prefix gs-gb;

  import goldstone-interfaces { prefix gs-if; }
  import goldstone-dpll { prefix gs-dpll; }

  organization
    "Goldstone";

  description
    "This module contains a collection of YANG definitions for
     managing gearboxes.";

  revision 2021-10-08 {
    description
      "Initial version.";
    reference
      "0.1.0";
  }

  grouping gearbox-connection-config {
    leaf client-interface {
      type gs-if:interface-ref;
    }
    leaf line-interface {
      type gs-if:interface-ref;
    }
  }

  grouping gearbox-connection-state {

  }

  grouping gearbox-connection-top {
    container connections {
      list connection {
        key "client-interface line-interface";
        leaf client-interface {
          type leafref {
            path "../config/client-interface";
          }
        }
        leaf line-interface {
          type leafref {
            path "../config/line-interface";
          }
        }
        container config {
          uses gearbox-connection-config;
        }
        container state {
          config false;
          uses gearbox-connection-config;
          uses gearbox-connection-state;
        }
      }
    }
  }

  grouping gearbox-synce-reference-clock-config {
    leaf name {
      type string;
    }
    leaf reference-interface {
      type gs-if:interface-ref;
    }
  }

  grouping gearbox-synce-reference-clock-state {
    container component-connection {
      leaf dpll {
        type leafref {
          path "/gs-dpll:dplls/gs-dpll:dpll/gs-dpll:name";
        }
      }
      leaf input-reference {
        type leafref {
          path "/gs-dpll:dplls/gs-dpll:dpll/gs-dpll:input-references/gs-dpll:input-reference/gs-dpll:name";
        }
      }
    }
  }

  grouping gearbox-synce-top {
    container synce-reference-clocks {
      list synce-reference-clock {
        key "name";
        leaf name {
          type leafref {
            path "../config/name";
          }
        }
        container config {
          uses gearbox-synce-reference-clock-config;
        }
        container state {
          config false;
          uses gearbox-synce-reference-clock-config;
          uses gearbox-synce-reference-clock-state;
        }
      }
    }
  }

  grouping gearbox-config {
    leaf name {
      type string;
    }
    leaf admin-status {
      type enumeration {
        enum UP;
        enum DOWN;
      }
      default UP;
    }

    leaf enable-flexible-connection {
      description
        "enabling this allows user to configure client-line interface connection flexibly.
        If true, only connections in the running datastore get configured in the hardware.
        If false, the system uses the default mapping. This can't be disabled if the running datastore
        contains configuration that conflicts with the default mapping. Enabling this without any configuration
        in the running datastore removes all connection hence no traffic forwarding happens.";
      type boolean;
      default false;
    }
  }

  grouping gearbox-state {
    leaf oper-status {
      type enumeration {
        enum UP;
        enum DOWN;
      }
    }
  }

  grouping gearbox-top {
    container gearboxes {
      list gearbox {
        key "name";
        leaf name {
          type leafref {
            path "../config/name";
          }
        }
        container config {
          uses gearbox-config;
        }
        container state {
          config false;
          uses gearbox-config;
          uses gearbox-state;
        }

        uses gearbox-connection-top;

        uses gearbox-synce-top;
      }
    }
  }

  uses gearbox-top;

  augment "/gs-if:interfaces/gs-if:interface/gs-if:state" {
    leaf associated-gearbox {
      type leafref {
        path "/gs-gb:gearboxes/gs-gb:gearbox/gs-gb:name";
      }
    }
    leaf is-connected {
      description
        "true when the interface is connected with another interface on the other side of the gearbox.
        when false, traffic can't traverse the gearbox";
      type boolean;
    }
  }

  deviation "/gs-if:interfaces/gs-if:interface/gs-if:config/gs-if:interface-type" {
      deviate add {
        default IF_ETHERNET;
      }
  }

  deviation "/gs-if:interfaces/gs-if:interface/gs-if:ethernet/gs-if:config/gs-if:fec" {
      deviate add {
        default RS;
      }
  }

  deviation "/gs-if:interfaces/gs-if:interface/gs-if:ethernet/gs-if:config/gs-if:mtu" {
    deviate replace {
      type uint16 {
        range "0..10000" {
          error-message "Invalid MTU value. valid range is 0..10000";
          error-app-tag mtu-invalid;
        }
      }
    }
    deviate add {
      default 10000;
    }
  }

}
