module goldstone-portchannel {

  yang-version "1";

  // namespace
  namespace "http://goldstone.net/yang/goldstone-portchannel";

  prefix "gs-lag";

  // import some basic types
  import goldstone-interfaces {
    prefix gs-if;
  }

  // meta
  organization
    "Goldstone";

  description
    "Goldstone portchannel";

  revision 2023-07-10 {
    description
      "Initial revision.";
  }


  // grouping statements

  grouping portchannel-config {
    description "portchannel configuration container.";

    leaf portchannel-id {
      type string{
        length 1..128;
        pattern 'PortChannel[0-9]{1,4}';
      }
      description "portchannel group id.";
    }

    leaf mtu {
      type uint16 {
        range "1312..9216" {
          error-message "Invalid MTU value";
          error-app-tag mtu-invalid;
        }
      }
      units "octets";
      default 9100;
    }

   leaf mode {
     type enumeration{
	enum dynamic;
	enum static;
      }
      description "portchannel mode";
    }

    uses gs-if:interface-common-config;

    leaf-list interface {
      type gs-if:interface-ref;
      description "List of interfaces to be combined";
    }

  }

  grouping portchannel-state {
    description "portchannel State variables container.";

    uses gs-if:interface-state;

    // placeholder
  }

  grouping portchannel-top {
    description "container for portchannel configuration.";

     container portchannel {
                description "Container for portchannel configuration and
      state variables";

      list portchannel-group {
        key "portchannel-id";

        description "Configured porcthannel keyed by portchannel-id";

        leaf portchannel-id {
          type leafref {
            path "../config/portchannel-id";
          }
          description "references the configured portchannel-id";
        }

        container config {
          description "Configuration parameters for portchannel";

          uses portchannel-config;
        }

        container state {
          config false;
          description "State variables for portchannel";

          uses portchannel-config;
          uses portchannel-state;
        }
      }
    }
  }
  uses portchannel-top;
}
