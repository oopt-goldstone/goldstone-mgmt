module goldstone-transponder {
  yang-version 1;
  namespace "http://goldstone.net/yang/transponder";
  prefix gs-transponder;

  revision 2019-11-01 {
    reference
      "0.1.0";
  }

  grouping transponder-module-config {
    leaf name {
      type string;
    }
    leaf admin-status {
      description
        "The admin state of the module";
      type enumeration {
        enum unknown;
        enum down;
        enum up;
      }
    }
    leaf enable-notify {
      description
        "Module generic notification";
      type boolean;
    }
  }

  grouping transponder-module-state {
    leaf id {
      type uint64;
    }
    leaf description {
      type string;
    }
    leaf location {
      description
        "The location of the module";
      type string;
    }
    leaf vendor-name {
      description
        "The module vendor's name";
      type string;
    }
    leaf vendor-part-number {
      description
        "The module vendor's part number";
      type string;
    }
    leaf vendor-serial-number {
      description
        "The module vendor's serial number";
      type string;
    }
    leaf firmware-version {
      description
        "The module firmware version";
      type string;
    }
    leaf oper-status {
      description
        "The operational state of the module";
      type enumeration {
        enum unknown;
        enum initialize;
        enum ready;
      }
    }
    leaf temp {
      description
        "The internal temperature of the module";
      type decimal64 {
        fraction-digits 16;
      }
    }
    leaf power {
      description
        "The power supply voltage";
      type decimal64 {
        fraction-digits 16;
      }
    }
    leaf num-host-interfaces {
      description
        "The number of host interfaces on the module";
      type uint32;
    }
    leaf num-network-interfaces {
      description
        "The number of network interfaces on the module";
      type uint32;
    }
    leaf cfp2aco-vendor-name {
      description
        "The CFP2ACO module vendor name";
      type string;
    }
    leaf cfp2aco-vendor-oui {
      description
        "The CFP2ACO module vendor OUI";
      type uint32;
    }
    leaf cfp2aco-vendor-part-number {
      description
        "The CFP2ACO module vendor's part number";
      type string;
    }
    leaf cfp2aco-vendor-serial-number {
      description
        "The CFP2ACO module vendor's serial number";
      type string;
    }
    leaf cfp2aco-firmware-version {
      description
        "The CFP2ACO module firmware version";
      type string;
    }
    leaf libtai-version {
      description
        "The version string of libtai";
      type string;
    }
  }

  grouping transponder-host-interface-config {
    leaf name {
      type string;
    }
    leaf signal-rate {
      description
        "signal rate";
      type enumeration {
        enum unknown;
        enum 100-gbe;
        enum 200-gbe;
        enum 400-gbe;
        enum otu4;
      }
    }
    leaf fec-type {
      description
        "FEC type";
      type enumeration {
        enum none;
        enum rs;
        enum fc;
        enum gfec;
      }
    }
    leaf loopback-type {
      description
        "Loopback type";
      type enumeration {
        enum none;
        enum shallow;
        enum deep;
      }
    }
    leaf enable-notify {
      description
        "Host interface generic notification";
      type boolean;
    }
    leaf enable-alarm-notification {
      description
        "Host interface alarm notification";
      type boolean;
    }
  }

  grouping transponder-host-interface-state {
    leaf id {
      type uint64;
    }
    leaf description {
      type string;
    }
    leaf index {
      description
        "The location of the host interface";
      type uint32;
    }
    leaf-list tx-align-status {
      description
        "TX Alignment Status";
      type enumeration {
        enum cdr-lock-fault;
        enum loss;
        enum out;
        enum deskew-lock;
      }
    }
    leaf ethernet-in-octets {
      type uint32;
    }
    leaf ethernet-in-packets {
      type uint32;
    }
    leaf ethernet-in-fcs-errors {
      type uint32;
    }
    leaf ethernet-in-mac-errors {
      type uint32;
    }
    leaf ethernet-out-octets {
      type uint32;
    }
    leaf ethernet-out-packets {
      type uint32;
    }
    leaf ethernet-out-fcs-errors {
      type uint32;
    }
    leaf ethernet-out-mac-errors {
      type uint32;
    }
    leaf-list tx-pcs-alarm {
      description
        "TX Ethernet PCS Alarm";
      type enumeration {
        enum loss-of-signal;
        enum loss-of-frame;
        enum illegal-alignment-marker;
        enum remote-fault;
        enum local-fault;
        enum hi-ber;
        enum bip-error;
        enum deskew-error;
      }
    }
    leaf-list rx-pcs-alarm {
      description
        "RX Ethernet PCS Alarm";
      type enumeration {
        enum loss-of-signal;
        enum loss-of-frame;
        enum illegal-alignment-marker;
        enum remote-fault;
        enum local-fault;
        enum hi-ber;
        enum bip-error;
        enum deskew-error;
      }
    }
  }

  grouping transponder-network-interface-config {
    leaf name {
      type string;
    }
    leaf tx-dis {
      description
        "TX Disable";
      type boolean;
    }
    leaf output-power {
      description
        "The TX output power in dBm";
      type decimal64 {
        fraction-digits 16;
      }
    }
    leaf tx-laser-freq {
      description
        "The TX laser frequency in Hz";
      type uint64;
    }
    leaf tx-fine-tune-laser-freq {
      description
        "The TX laser fine tune frequency in Hz";
      type int64;
    }
    leaf line-rate {
      description
        "The line rate";
      type enumeration {
        enum unknown;
        enum 100g;
        enum 200g;
        enum 300g;
        enum 400g;
      }
    }
    leaf modulation-format {
      description
        "The modulation format";
      type enumeration {
        enum unknown;
        enum bpsk;
        enum dp-bpsk;
        enum qpsk;
        enum dp-qpsk;
        enum 8-qam;
        enum dp-8-qam;
        enum 16-qam;
        enum dp-16-qam;
        enum 32-qam;
        enum dp-32-qam;
        enum 64-qam;
        enum dp-64-qam;
        enum dp-16-qam-ps;
      }
    }
    leaf fec-type {
      description
        "The FEC type";
      type enumeration {
        enum unknown;
        enum sc-fec;
        enum cfec;
        enum ofec;
        enum hg-fec;
        enum none;
      }
    }
    leaf client-signal-mapping-type {
      description
        "The client signal mapping type";
      type enumeration {
        enum unknown;
        enum otu4-lr;
        enum flexo-lr;
        enum zr;
        enum otuc2;
      }
    }
    leaf differential-encoding {
      description
        "Differential phase encoding";
      type boolean;
    }
    leaf pulse-shaping-tx {
      description
        "Pulse shaping enabled on TX";
      type boolean;
    }
    leaf pulse-shaping-rx {
      description
        "Pulse shaping enabled on RX";
      type boolean;
    }
    leaf pulse-shaping-tx-beta {
      description
        "Pulse shaping beta on TX";
      type decimal64 {
        fraction-digits 16;
      }
    }
    leaf pulse-shaping-rx-beta {
      description
        "Pulse shaping beta on RX";
      type decimal64 {
        fraction-digits 16;
      }
    }
    leaf voa-rx {
      description
        "RX VOA attenuation in dB";
      type decimal64 {
        fraction-digits 16;
      }
    }
    leaf loopback-type {
      description
        "Loopback type";
      type enumeration {
        enum none;
        enum shallow;
        enum deep;
      }
    }
    leaf prbs-type {
      description
        "PRBS type";
      type enumeration {
        enum none;
        enum prbs7;
        enum prbs9;
        enum prbs11;
        enum prbs15;
        enum prbs20;
        enum prbs23;
        enum prbs31;
      }
    }
    leaf ch1-freq {
      description
        "Channel 1 frequency in Hz";
      type uint64;
    }
    leaf enable-notify {
      description
        "Network interface generic notification";
      type boolean;
    }
    leaf enable-alarm-notification {
      description
        "Network interface alarm notification";
      type boolean;
    }
    leaf losi {
      description
        "loss of signal detection setting";
      type boolean;
    }
    leaf ber-period {
      type uint32;
    }
    leaf hd-fec-type {
      description
        "HD-FEC type";
      type enumeration {
        enum none;
        enum gfec;
        enum hgfec;
      }
    }
    leaf sd-fec-type {
      description
        "SD-FEC type";
      type enumeration {
        enum none;
        enum on;
      }
    }
    leaf mld {
      description
        "MLD setting";
      type enumeration {
        enum unknown;
        enum 4-lanes;
        enum 20-lanes;
      }
    }
  }

  grouping transponder-network-interface-state {
    leaf id {
      type uint64;
    }
    leaf description {
      type string;
    }
    leaf index {
      description
        "The location of the network interface";
      type uint32;
    }
    leaf-list tx-align-status {
      description
        "The transmit alignment status";
      type enumeration {
        enum loss;
        enum out;
        enum cmu-lock;
        enum ref-clock;
        enum timing;
      }
    }
    leaf-list rx-align-status {
      description
        "The receive alignment status";
      type enumeration {
        enum modem-sync;
        enum modem-lock;
        enum loss;
        enum out;
        enum timing;
      }
    }
    leaf tx-grid-spacing {
      description
        "TX Grid Spacing";
      type enumeration {
        enum unknown;
        enum 100-ghz;
        enum 50-ghz;
        enum 33-ghz;
        enum 25-ghz;
        enum 12-5-ghz;
        enum 6-25-ghz;
      }
    }
    leaf current-output-power {
      description
        "The current measured TX output power in dBm";
      type decimal64 {
        fraction-digits 16;
      }
    }
    leaf current-pre-fec-ber {
      description
        "The current pre-FEC bit error rate";
      type binary {
        length "4";
      }
    }
    leaf current-ber-period {
      description
        "The time period over which the current pre-FEC bit error rate was";
      type uint32;
    }
    leaf oper-status {
      description
        "The operational state of the network interface";
      type enumeration {
        enum unknown;
        enum reset;
        enum initialize;
        enum low-power;
        enum high-power-up;
        enum tx-off;
        enum tx-turn-on;
        enum ready;
        enum tx-turn-off;
        enum high-power-down;
        enum fault;
      }
    }
    leaf min-laser-freq {
      description
        "The TX/RX minimum laser frequency in Hz";
      type uint64;
    }
    leaf max-laser-freq {
      description
        "The TX/RX maximum laster frequency in Hz";
      type uint64;
    }
    leaf-list laser-grid-support {
      description
        "The laser grid spacing support. A bitfield of the supported grid";
      type enumeration {
        enum unknown;
        enum 100-ghz;
        enum 50-ghz;
        enum 33-ghz;
        enum 25-ghz;
        enum 12-5-ghz;
        enum 6-25-ghz;
      }
    }
    leaf current-input-power {
      description
        "The total current RX input power in dBm";
      type decimal64 {
        fraction-digits 16;
      }
    }
    leaf current-post-voa-total-power {
      description
        "The total current post-VOA RX input power in dBm";
      type decimal64 {
        fraction-digits 16;
      }
    }
    leaf current-provisioned-channel-power {
      description
        "The current RX input power in the provisioned channel in dBm";
      type decimal64 {
        fraction-digits 16;
      }
    }
    leaf current-tx-laser-freq {
      description
        "The current TX laser frequency in Hz";
      type uint64;
    }
    leaf-list rx-otu-status {
      description
        "Rx OTU Status with Open ROADM Multi-Source Agreement";
      type enumeration {
        enum loss-of-frame;
        enum loss-of-multiframe;
        enum backward-defect-indication;
        enum alarm-indication-signal;
        enum err;
      }
    }
    leaf-list rx-odu-status {
      description
        "Rx ODU Status with Open ROADM Multi-Source Agreement";
      type enumeration {
        enum backward-defect-indication;
        enum alarm-indication-signal;
        enum open-connection-indication;
        enum locked-defect;
        enum err;
      }
    }
    leaf-list rx-opu-status {
      description
        "Rx OPU Status with Open ROADM Multi-Source Agreement";
      type enumeration {
        enum payload-mismatch;
        enum client-signal-fail;
        enum err;
      }
    }
    leaf-list rx-ts-status {
      description
        "Rx Training Sequence Status";
      type enumeration {
        enum loss-of-lock;
        enum err;
      }
    }
    leaf current-chromatic-dispersion {
      description
        "Current Chromatic Dispersion (CD) in ps/nm";
      type uint64;
    }
    leaf current-differential-group-delay {
      description
        "Current Differential Group Delay (DGD) in ps";
      type uint32;
    }
    leaf current-snr {
      description
        "Current Signal-to-Noise Ratio (SNR) in dB";
      type decimal64 {
        fraction-digits 16;
      }
    }
    leaf current-post-fec-ber {
      description
        "The current post-FEC bit error rate";
      type binary {
        length "4";
      }
    }
    leaf current-prbs-ber {
      description
        "The current PRBS bit error rate";
      type binary {
        length "4";
      }
    }
    leaf current-post-voa-provisioned-channel-power {
      description
        "The current post-VOA RX input power in the provisioned channel in dBm";
      type decimal64 {
        fraction-digits 16;
      }
    }
    leaf rx-los {
      description
        "RX LOS alarm";
      type boolean;
    }
    leaf rx-q-mergin {
      description
        "Network RX Q margin over PM interval";
      type decimal64 {
        fraction-digits 16;
      }
    }
    leaf uncorrected-block-count {
      description
        "Network FEC Uncorrected Blocks Count Over PM interval";
      type uint32;
    }
    leaf-list al-dsp-sync {
      description
        "AL_DSP_SYNC (0x9190)";
      type enumeration {
        enum ref-sync;
        enum line-sync;
        enum client-sync-cha;
        enum client-sync-chb;
        enum client-sync-chc;
        enum client-sync-chd;
        enum line-frame-sync;
      }
    }
    leaf rx-freq-offset {
      description
        "RX current carrier frequency offset in Hz";
      type int64;
    }
    leaf tx-laser-bias {
      description
        "TAI_NETWORK_INTERFACE_ATTR_TX_LASER_BIAS (0xB320)";
      type uint16;
    }
    leaf sync-error {
      type boolean;
    }
    leaf dsp-oper-status {
      type enumeration {
        enum unknown;
        enum no-module;
        enum waiting-configuration;
        enum booting-first-half;
        enum waiting-aco-module;
        enum booting-aco-module;
        enum waiting-rx-signal;
        enum booting-second-half;
        enum ready;
        enum misc-config;
      }
    }
    leaf disable-constellation {
      type boolean;
    }
    leaf prbs-in-sync {
      description
        "PRBS in-sync";
      type boolean;
    }
    leaf loaded-libaco {
      description
        "The loaded libaco library name";
      type string;
    }
  }

  grouping transponder-component-top {
    container modules {
      list module {
        key "name";
        leaf name {
          type leafref {
            path "../config/name";
          }
        }
        container config {
          uses transponder-module-config;
        }
        container state {
          config false;
          uses transponder-module-config;
          uses transponder-module-state;
        }
        list network-interface {
          key "name";
          leaf name {
            type leafref {
              path "../config/name";
            }
          }
          container config {
            uses transponder-network-interface-config;
          }
          container state {
            config false;
            uses transponder-network-interface-config;
            uses transponder-network-interface-state;
          }
        }
        list host-interface {
          key "name";
          leaf name {
            type leafref {
              path "../config/name";
            }
          }
          container config {
            uses transponder-host-interface-config;
          }
          container state {
            config false;
            uses transponder-host-interface-config;
            uses transponder-host-interface-state;
          }
        }
      }
    }
  }

  uses transponder-component-top;

  notification module-notify-event {
    leaf-list keys {
      type string;
      description
        "list of valid attribute name stored in the event";
    }
    leaf module-name {
      type string;
    }
    uses transponder-module-config;
    uses transponder-module-state;
  }

  notification host-interface-notify-event {
    leaf-list keys {
      type string;
      description
        "list of valid attribute name stored in the event";
    }
    leaf module-name {
      type string;
    }
    uses transponder-host-interface-config;
    uses transponder-host-interface-state;
  }

  notification host-interface-alarm-notification-event {
    leaf-list keys {
      type string;
      description
        "list of valid attribute name stored in the event";
    }
    leaf module-name {
      type string;
    }
    uses transponder-host-interface-config;
    uses transponder-host-interface-state;
  }

  notification network-interface-notify-event {
    leaf-list keys {
      type string;
      description
        "list of valid attribute name stored in the event";
    }
    leaf module-name {
      type string;
    }
    uses transponder-network-interface-config;
    uses transponder-network-interface-state;
  }

  notification network-interface-alarm-notification-event {
    leaf-list keys {
      type string;
      description
        "list of valid attribute name stored in the event";
    }
    leaf module-name {
      type string;
    }
    uses transponder-network-interface-config;
    uses transponder-network-interface-state;
  }
}
