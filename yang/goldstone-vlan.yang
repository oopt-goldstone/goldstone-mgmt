module goldstone-vlan {

  yang-version "1";

  namespace "http://goldstone.net/yang/goldstone-vlan"; 
  prefix gs-vlan;

  import goldstone-interfaces { prefix gs-if; }

  organization
    "GoldStone";

  contact
    "Goldstone";

  description
    "Goldstone VLAN";

  revision 2020-10-13 {
    description
      "Initial revision.";
  }

  typedef vlan-id {
    type uint16 {
      range 1..4094;
    }
  }

  typedef vlan-mode-type {
    type enumeration {
      enum ACCESS;
      enum TRUNK;
    }
  }

  grouping vlan-config {
    leaf vlan-id {
      type vlan-id;
    }

    leaf name {
      type string;
    }
  }

  grouping vlan-state {
  }

  grouping vlan-members-state {
    container members {
      leaf-list member {
        config false;
        type gs-if:interface-ref;
      }
    }
  }

  grouping vlan-top {
    container vlans {
      list vlan {
        key "vlan-id";

        leaf vlan-id {
          type leafref {
            path "../config/vlan-id";
          }
        }

        container config {
          uses vlan-config;
        }

        container state {
          config false;
          uses vlan-config;
          uses vlan-state;
        }
        uses vlan-members-state;
      }
    }
  }

  uses vlan-top;

  grouping vlan-switched-config {
    leaf interface-mode {
      type vlan-mode-type;
    }

    leaf access-vlan {
      when "../interface-mode = 'ACCESS'";
      type vlan-id;
    }

    leaf-list trunk-vlans {
      when "../interface-mode = 'TRUNK'";
      type vlan-id;
    }
  }

  grouping vlan-switched-state {
  }

  grouping vlan-switched-top {
    container switched-vlan {

      container config {
          uses vlan-switched-config;
      }

      container state {
        config false;

        uses vlan-switched-config;
        uses vlan-switched-state;
      }
    }
  }

  augment "/gs-if:interfaces/gs-if:interface" {
    description
      "Adds VLAN settings to individual Ethernet interfaces";

    uses vlan-switched-top;
  }

}
