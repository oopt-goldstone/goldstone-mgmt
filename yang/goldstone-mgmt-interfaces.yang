module goldstone-mgmt-interfaces {
  yang-version "1";
  namespace "http://goldstone.net/yang/gs-mgmt-interfaces";
  prefix gs-mgmt-if;

  import goldstone-interfaces {
    prefix gs-if;
  }

  organization
    "Goldstone";

  description
    "This module contains a collection of YANG definitions for
     managing management network interfaces.";

  revision 2020-10-13 {
    description
      "Initial revision.";
    reference
      "0.1.0";
  }

  revision 2022-09-09 {
    description
      "Overhauled. Make the structure idential to goldstone-interfaces model";
    reference
      "0.2.0";
  }

  typedef interface-ref {
    type leafref {
      path "/gs-mgmt-if:interfaces/gs-mgmt-if:interface/gs-mgmt-if:name";
    }
  }

  uses gs-if:interfaces-top;

  notification interface-link-state-notify-event {
    leaf if-name {
      type string;
    }

    uses gs-if:interface-state;
  }

  rpc clear-counters {
    output {
      leaf status {
        type enumeration {
          enum faliure;
          enum success;
        }
      }
    }
  }

  deviation "/gs-mgmt-if:interfaces/gs-mgmt-if:interface/gs-mgmt-if:config/gs-mgmt-if:admin-status" {
      deviate replace {
        default UP;
      }
  }

}
