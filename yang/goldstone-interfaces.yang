module goldstone-interfaces {

  yang-version "1";

  namespace "http://goldstone.net/yang/goldstone-interfaces";
  prefix gs-if;

  import ietf-yang-types {
    prefix yang;
  }

  organization
    "Goldstone";

  description
    "This module contains a collection of YANG definitions for
     managing network interfaces.";

  revision 2020-10-13 {
    description
      "Initial version.";
    reference
      "0.1.0";
  }


  /*
   * Typedefs
   */

  typedef interface-ref {
    type leafref {
      path "/gs-if:interfaces/gs-if:interface/gs-if:name";
    }
    description
      "This type is used by data models that need to reference
       interfaces.";
  }

  typedef interface-type {
    type enumeration {
      enum IF_ETHERNET;
      enum IF_OTN;
    }
  }

  typedef ethernet-speed {
    type enumeration {
      enum SPEED_UNKNOWN;
      enum SPEED_100M;
      enum SPEED_1000M;
      enum SPEED_2500M;
      enum SPEED_5000M;
      enum SPEED_10G;
      enum SPEED_20G;
      enum SPEED_25G;
      enum SPEED_40G;
      enum SPEED_50G;
      enum SPEED_100G;
      enum SPEED_200G;
      enum SPEED_400G;
    }
  }

  typedef interface-pin-mode {
    type enumeration {
      enum NRZ;
      enum PAM4;
    }
  }

  /*
   * Data nodes
   */

  grouping ethernet-port-breakout-config {
    leaf num-channels {
      type uint8;
      description
        "Sets the number of channels to 'breakout' on a port
        capable of channelization";
    }

    leaf channel-speed {
      type ethernet-speed;
      description
        "Sets the channel speed on each channel -- the
        supported values are defined by the
        ETHERNET_SPEED identity";
    }
  }

  grouping ethernet-port-breakout-state {
    leaf parent {
      must "not(../num-channels) and not(../channel-speed)" {
        error-message "Sub-interface should not have num-channels and channel-speed configured";
      }
      type interface-ref;
    }
    leaf-list children {
      type interface-ref;
    }
  }

  grouping ethernet-port-breakout-top {
    container breakout {
      container config {
        uses ethernet-port-breakout-config;
      }
      container state {
        config false;
        uses ethernet-port-breakout-config;
        uses ethernet-port-breakout-state;
      }
    }
  }

  grouping ethernet-auto-negotiate-config {
    leaf enabled {
      type boolean;
      default false;
    }
    leaf-list advertised-speeds {
      type ethernet-speed;
    }
  }

  grouping ethernet-auto-negotiate-state {
    leaf-list capable-speeds {
      type ethernet-speed;
    }
    leaf-list status {
      type enumeration {
        enum resolved;
        enum incompatible-link;
        enum link-fail-inhibit-timeout;
        enum completed;
        enum fatal-error;
      }
    }
  }

  grouping ethernet-auto-negotiate-top {
    container auto-negotiate {
      container config {
        uses ethernet-auto-negotiate-config;
      }
      container state {
        config false;
        uses ethernet-auto-negotiate-config;
        uses ethernet-auto-negotiate-state;
      }
    }
  }

  grouping ethernet-pcs-config {

  }

  grouping ethernet-pcs-state-counters {
    leaf bip-error {
      type yang:counter32;
    }
    leaf virtual-lane-loss {
      type yang:counter32;
    }
    leaf serdes-lane-fec-symbol-error {
      type yang:counter32;
    }
    leaf corrected-fec-error {
      type yang:counter32;
    }
    leaf uncorrected-fec-error {
      type yang:counter32;
    }
    leaf fec-symbol-error {
      type yang:counter32;
    }
    leaf fc-fec-corrected-error {
      type yang:counter32;
    }
    leaf fc-fec-uncorrected-error {
      type yang:counter32;
    }
    leaf sync-header-error {
      type yang:counter32;
    }
    leaf hiber {
      type yang:counter32;
    }
    leaf test-pattern-error {
      type yang:counter32;
    }
    leaf loss-of-block-lock {
      type yang:counter32;
    }
    leaf ber-elapsed-sec {
      type uint32;
    }
    leaf ber-elapsed-usec {
      type uint32;
    }
  }

  grouping ethernet-pcs-state {
    leaf-list pcs-status {
      type enumeration {
        enum ready;
        enum block-locked;
        enum alignment-locked;
        enum rx-remote-fault;
        enum rx-local-fault;
      }
    }

    leaf-list serdes-status {
      type enumeration {
        enum tx-ready;
        enum rx-ready;
        enum lane-adapt-done;
        enum dlos;
        enum pll-locked;
        enum signal-detect;
        enum phy-ready;
        enum tx-fifo-overflow;
        enum rx-fifo-overflow;
      }
    }

    container counters {
      uses ethernet-pcs-state-counters;
    }
  }

  grouping ethernet-pcs-top {
    container pcs {
      container config {
        uses ethernet-pcs-config;
      }
      container state {
        config false;
        uses ethernet-pcs-config;
        uses ethernet-pcs-state;
      }
    }
  }

  grouping ethernet-interface-config {

    leaf mac-address {
      type yang:phys-address;
    }

    leaf mtu {
      type uint16;
      units "octets";
    }

    leaf fec {
      when "../../auto-negotiate/config/enabled = 'false'";
      type enumeration {
        enum FC;
        enum RS;
        enum NONE;
      }
    }

    leaf interface-type {
      when "../../auto-negotiate/config/enabled = 'false'";
      type enumeration {
        enum SR;
        enum SR2;
        enum SR4;
        enum CR;
        enum CR2;
        enum CR4;
        enum LR;
        enum LR2;
        enum LR4;
        enum KR;
        enum KR2;
        enum KR4;
        enum SFI;
        enum XFI;
        enum XLAUI;
      }
    }

    leaf speed {
      when "../../auto-negotiate/config/enabled = 'false'";
      type ethernet-speed;
    }
  }

  grouping ethernet-mac-rx-state-counters {
    leaf rx-octets-all {
      type yang:counter64;
    }
    leaf rx-octets-good {
      type yang:counter64;
    }
    leaf rx-pkts-all {
      type yang:counter64;
    }
    leaf rx-pkts-good {
      type yang:counter64;
    }
    leaf rx-pkts-err {
      type yang:counter64;
    }
    leaf rx-pkts-long {
      type yang:counter64;
    }
    leaf rx-pkts-crc-err {
      type yang:counter64;
    }
    leaf rx-pkts-all-crc-err {
      type yang:counter64;
    }
    leaf rx-pkts-jabber {
      type yang:counter64;
    }
    leaf rx-pkts-stomped {
      type yang:counter64;
    }
    leaf rx-pkts-vlan {
      type yang:counter64;
    }
    leaf rx-pkts-mac-ctrl {
      type yang:counter64;
    }
    leaf rx-pkts-broadcast {
      type yang:counter64;
    }
    leaf rx-pkts-multicast {
      type yang:counter64;
    }
    leaf rx-pkts-unicast {
      type yang:counter64;
    }
    leaf rx-pkts-0-63-b {
      type yang:counter64;
    }
    leaf rx-pkts-64-b {
      type yang:counter64;
    }
    leaf rx-pkts-65-127-b {
      type yang:counter64;
    }
    leaf rx-pkts-128-255-b {
      type yang:counter64;
    }
    leaf rx-pkts-256-511-b {
      type yang:counter64;
    }
    leaf rx-pkts-512-1023-b {
      type yang:counter64;
    }
    leaf rx-pkts-1024-1518-b {
      type yang:counter64;
    }
    leaf rx-pkts-1519-2047-b {
      type yang:counter64;
    }
    leaf rx-pkts-2048-4095-b {
      type yang:counter64;
    }
    leaf rx-pkts-4096-8191-b {
      type yang:counter64;
    }
    leaf rx-pkts-8192-max-b {
      type yang:counter64;
    }
    leaf rx-err-blk {
      type yang:counter64;
    }
    leaf rx-valid-err-blk {
      type yang:counter64;
    }
    leaf rx-unknown-err-blk {
      type yang:counter64;
    }
    leaf rx-inv-err-blk {
      type yang:counter64;
    }
    leaf rx-pkts-pause {
      type yang:counter64;
    }
    leaf rx-pkts-pause-pfc0 {
      type yang:counter64;
    }
    leaf rx-pkts-pfc1 {
      type yang:counter64;
    }
    leaf rx-pkts-pfc2 {
      type yang:counter64;
    }
    leaf rx-pkts-pfc3 {
      type yang:counter64;
    }
    leaf rx-pkts-pfc4 {
      type yang:counter64;
    }
    leaf rx-pkts-pfc5 {
      type yang:counter64;
    }
    leaf rx-pkts-pfc6 {
      type yang:counter64;
    }
    leaf rx-pkts-pfc7 {
      type yang:counter64;
    }
    leaf rx-pkts-link-pause {
      type yang:counter64;
    }
  }

  grouping ethernet-mac-tx-state-counters {
    leaf tx-octets-all {
      type yang:counter64;
    }
    leaf tx-octets-good {
      type yang:counter64;
    }
    leaf tx-pkts-all {
      type yang:counter64;
    }
    leaf tx-pkts-good {
      type yang:counter64;
    }
    leaf tx-pkts-err {
      type yang:counter64;
    }
    leaf tx-pkts-unicast {
      type yang:counter64;
    }
    leaf tx-pkts-multicast {
      type yang:counter64;
    }
    leaf tx-pkts-broadcast {
      type yang:counter64;
    }
    leaf tx-pkts-pause {
      type yang:counter64;
    }
    leaf tx-pkts-pause-pfc0 {
      type yang:counter64;
    }
    leaf tx-pkts-pfc1 {
      type yang:counter64;
    }
    leaf tx-pkts-pfc2 {
      type yang:counter64;
    }
    leaf tx-pkts-pfc3 {
      type yang:counter64;
    }
    leaf tx-pkts-pfc4 {
      type yang:counter64;
    }
    leaf tx-pkts-pfc5 {
      type yang:counter64;
    }
    leaf tx-pkts-pfc6 {
      type yang:counter64;
    }
    leaf tx-pkts-pfc7 {
      type yang:counter64;
    }
    leaf tx-pkts-vlan {
      type yang:counter64;
    }
    leaf tx-pkts-0-63-b {
      type yang:counter64;
    }
    leaf tx-pkts-64-b {
      type yang:counter64;
    }
    leaf tx-pkts-65-127-b {
      type yang:counter64;
    }
    leaf tx-pkts-128-255-b {
      type yang:counter64;
    }
    leaf tx-pkts-256-511-b {
      type yang:counter64;
    }
    leaf tx-pkts-512-1023-b {
      type yang:counter64;
    }
    leaf tx-pkts-1024-1518-b {
      type yang:counter64;
    }
    leaf tx-pkts-1519-2047-b {
      type yang:counter64;
    }
    leaf tx-pkts-2048-4095-b {
      type yang:counter64;
    }
    leaf tx-pkts-4096-8191-b {
      type yang:counter64;
    }
    leaf tx-pkts-8192-max-b {
      type yang:counter64;
    }
    leaf tx-pkts-drained {
      type yang:counter64;
    }
    leaf tx-pkts-jabbered {
      type yang:counter64;
    }
    leaf tx-pkts-padded {
      type yang:counter64;
    }
    leaf tx-pkts-trunc {
      type yang:counter64;
    }
  }

  grouping ethernet-interface-state {
      container counters {
        uses ethernet-mac-rx-state-counters;
        uses ethernet-mac-tx-state-counters;
      }
  }

  grouping ethernet-top {
    container ethernet {
      container config {
        uses ethernet-interface-config;
      }

      container state {
        config false;
        uses ethernet-interface-config;
        uses ethernet-interface-state;
      }

      uses ethernet-port-breakout-top;
      uses ethernet-auto-negotiate-top;
      uses ethernet-pcs-top;
    }
  }

  grouping otn-interface-config {
    leaf mfi-type {
      type enumeration {
        enum OTL;
        enum FOIC;
      }
    }
  }

  grouping otn-interface-state {
  }

  grouping otn-top {
    container otn {
      container config {
        uses otn-interface-config;
      }
      container state {
        config false;
        uses otn-interface-config;
        uses otn-interface-state;
      }
    }
  }

  grouping interface-state {
    leaf oper-status {
      type enumeration {
        enum UP;
        enum DOWN;
        enum DORMANT;
      }
      description
        "The current operational state of the interface.
         This leaf has the same semantics as ifOperStatus.";
      reference
        "RFC 2863: The Interfaces Group MIB - ifOperStatus";
    }

    leaf lanes {
      type string;
    }

    leaf alias {
      type string;
    }

    leaf current-prbs-ber {
      description
        "The current PRBS bit error rate. encoded as IEEE 32-bit floating point number";
      type binary {
        length "4";
      }
    }

  }

  grouping interface-counters-state {

    container counters {
      description
        "A collection of interface-related statistics objects.";

      leaf in-octets {
        type yang:counter64;
        description
          "The total number of octets received on the interface,
           including framing characters.

           Discontinuities in the value of this counter can occur
           at re-initialization of the management system and at
           other times as indicated by the value of
           'discontinuity-time'.";
        reference
          "RFC 2863: The Interfaces Group MIB - ifHCInOctets";
      }

      leaf in-unicast-pkts {
        type yang:counter64;
        description
          "The number of packets, delivered by this sub-layer to a
           higher (sub-)layer, that were not addressed to a
           multicast or broadcast address at this sub-layer.

           Discontinuities in the value of this counter can occur
           at re-initialization of the management system and at
           other times as indicated by the value of
           'discontinuity-time'.";
        reference
          "RFC 2863: The Interfaces Group MIB - ifHCInUcastPkts";
      }

      leaf in-broadcast-pkts {
        type yang:counter64;
        description
          "The number of packets, delivered by this sub-layer to a
           higher (sub-)layer, that were addressed to a broadcast
           address at this sub-layer.

           Discontinuities in the value of this counter can occur
           at re-initialization of the management system and at
           other times as indicated by the value of
           'discontinuity-time'.";
        reference
          "RFC 2863: The Interfaces Group MIB -
                     ifHCInBroadcastPkts";
      }

      leaf in-multicast-pkts {
        type yang:counter64;
        description
          "The number of packets, delivered by this sub-layer to a
           higher (sub-)layer, that were addressed to a multicast
           address at this sub-layer.  For a MAC-layer protocol,
           this includes both Group and Functional addresses.

           Discontinuities in the value of this counter can occur
           at re-initialization of the management system and at
           other times as indicated by the value of
           'discontinuity-time'.";
        reference
          "RFC 2863: The Interfaces Group MIB -
                     ifHCInMulticastPkts";
      }

      leaf in-discards {
        type yang:counter64;
        description
          "The number of inbound packets that were chosen to be
           discarded even though no errors had been detected to
           prevent their being deliverable to a higher-layer
           protocol.  One possible reason for discarding such a
           packet could be to free up buffer space.

           Discontinuities in the value of this counter can occur
           at re-initialization of the management system and at
           other times as indicated by the value of
           'discontinuity-time'.";
        reference
          "RFC 2863: The Interfaces Group MIB - ifInDiscards";
      }

      leaf in-errors {
        type yang:counter64;
        description
          "For packet-oriented interfaces, the number of inbound
           packets that contained errors preventing them from being
           deliverable to a higher-layer protocol.  For character-
           oriented or fixed-length interfaces, the number of
           inbound transmission units that contained errors
           preventing them from being deliverable to a higher-layer
           protocol.

           Discontinuities in the value of this counter can occur
           at re-initialization of the management system and at
           other times as indicated by the value of
           'discontinuity-time'.";
        reference
          "RFC 2863: The Interfaces Group MIB - ifInErrors";
      }

      leaf in-unknown-protos {
        type yang:counter64;

        description
          "For packet-oriented interfaces, the number of packets
           received via the interface that were discarded because
           of an unknown or unsupported protocol.  For
           character-oriented or fixed-length interfaces that
           support protocol multiplexing, the number of
           transmission units received via the interface that were
           discarded because of an unknown or unsupported protocol.
           For any interface that does not support protocol
           multiplexing, this counter is not present.

           Discontinuities in the value of this counter can occur
           at re-initialization of the management system and at
           other times as indicated by the value of
           'discontinuity-time'.";
        reference
          "RFC 2863: The Interfaces Group MIB - ifInUnknownProtos";
      }

      leaf out-octets {
        type yang:counter64;
        description
          "The total number of octets transmitted out of the
           interface, including framing characters.

           Discontinuities in the value of this counter can occur
           at re-initialization of the management system and at
           other times as indicated by the value of
           'discontinuity-time'.";
        reference
          "RFC 2863: The Interfaces Group MIB - ifHCOutOctets";
      }

      leaf out-unicast-pkts {
        type yang:counter64;
        description
          "The total number of packets that higher-level protocols
           requested be transmitted and that were not addressed
           to a multicast or broadcast address at this sub-layer,
           including those that were discarded or not sent.

           Discontinuities in the value of this counter can occur
           at re-initialization of the management system and at
           other times as indicated by the value of
           'discontinuity-time'.";
        reference
          "RFC 2863: The Interfaces Group MIB - ifHCOutUcastPkts";
      }

      leaf out-broadcast-pkts {
        type yang:counter64;
        description
          "The total number of packets that higher-level protocols
           requested be transmitted and that were addressed to a
           broadcast address at this sub-layer, including those
           that were discarded or not sent.

           Discontinuities in the value of this counter can occur
           at re-initialization of the management system and at
           other times as indicated by the value of
           'discontinuity-time'.";
        reference
          "RFC 2863: The Interfaces Group MIB -
                     ifHCOutBroadcastPkts";
      }

      leaf out-multicast-pkts {
        type yang:counter64;
        description
          "The total number of packets that higher-level protocols
           requested be transmitted and that were addressed to a
           multicast address at this sub-layer, including those
           that were discarded or not sent.  For a MAC-layer
           protocol, this includes both Group and Functional
           addresses.

           Discontinuities in the value of this counter can occur
           at re-initialization of the management system and at
           other times as indicated by the value of
           'discontinuity-time'.";
        reference
          "RFC 2863: The Interfaces Group MIB -
                     ifHCOutMulticastPkts";
      }

      leaf out-discards {
        type yang:counter64;
        description
          "The number of outbound packets that were chosen to be
           discarded even though no errors had been detected to
           prevent their being transmitted.  One possible reason
           for discarding such a packet could be to free up buffer
           space.

           Discontinuities in the value of this counter can occur
           at re-initialization of the management system and at
           other times as indicated by the value of
           'discontinuity-time'.";
        reference
          "RFC 2863: The Interfaces Group MIB - ifOutDiscards";
      }

      leaf out-errors {
        type yang:counter64;
        description
          "For packet-oriented interfaces, the number of outbound
           packets that could not be transmitted because of errors.
           For character-oriented or fixed-length interfaces, the
           number of outbound transmission units that could not be
           transmitted because of errors.

           Discontinuities in the value of this counter can occur
           at re-initialization of the management system and at
           other times as indicated by the value of
           'discontinuity-time'.";
        reference
          "RFC 2863: The Interfaces Group MIB - ifOutErrors";
      }
    }
  }

  grouping interface-common-config {
    description
      "Configuration data data nodes common to physical interfaces
      and subinterfaces";

    leaf name {
      type string;
    }

    leaf description {
      type string;
      reference
        "RFC 2863: The Interfaces Group MIB - ifAlias";
    }

    leaf admin-status {
      type enumeration {
        enum UP;
        enum DOWN;
      }
      default DOWN;
      description
        "The desired state of the interface.

         This leaf has the same read semantics as ifAdminStatus.";
      reference
        "RFC 2863: The Interfaces Group MIB - ifAdminStatus";
    }
  }

  grouping interface-config {
    leaf interface-type {
      type interface-type;
    }

    leaf pin-mode {
      type interface-pin-mode;
    }

    leaf loopback-mode {
      type enumeration {
        enum NONE;
        enum SHALLOW;
        enum DEEP;
      }
      default NONE;
    }

    leaf prbs-mode {
      type enumeration {
        enum NONE;
        enum PRBS7;
        enum PRBS9;
        enum PRBS11;
        enum PRBS15;
        enum PRBS20;
        enum PRBS23;
        enum PRBS31;
      }
      default NONE;
    }
  }

  grouping interfaces-top {
    container interfaces {
      list interface {
        key "name";
        leaf name {
          type leafref {
            path "../config/name";
          }
        }
        container config {
          uses interface-common-config;
          uses interface-config;
        }
        container state {
          config false;
          uses interface-common-config;
          uses interface-config;
          uses interface-state;
          uses interface-counters-state;
        }

        uses ethernet-top;
        uses otn-top;
      }
    }
  }

  uses interfaces-top;

  /*
   * Notifications
   */

  notification interface-link-state-notify-event {
    leaf if-name {
      type string;
    }

    uses interface-state;
  }

  rpc clear-counters {
    output {
      leaf status {
        type enumeration {
          enum faliure;
          enum success;
        }
      }
    }
  }
}
